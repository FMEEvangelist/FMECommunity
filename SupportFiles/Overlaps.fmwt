FME workspace Overlaps.fmwt
Title: DGNV8 to NONE

Parameters:
- SourceDataset_DGNV8 = $(FME_MF_DIR)1/Transportation/RoadsDGN.dgn   # Source Bentley MicroStation Design File(s)

Readers:
- DGNV8_1: DGNV8 from $(SourceDataset_DGNV8)

Arterial (reader DGNV8_1)
    -> FeatureColorSetter
Collector (reader DGNV8_1)
    -> FeatureColorSetter
NonCity (reader DGNV8_1)
    -> FeatureColorSetter
Other (reader DGNV8_1)
    -> FeatureColorSetter
Private (reader DGNV8_1)
    -> FeatureColorSetter
Residential (reader DGNV8_1)
    -> FeatureColorSetter
Secondary (reader DGNV8_1)
    -> FeatureColorSetter
FeatureColorSetter
    COLOR = 0,0,0.498039
    MODE = Fixed
    COLORED -> Counter
    COLORED -> Snipper_2
    COLORED -> Snipper
Note: Snipping Mode: Vertex / Starting Vertex: 0 / Ending Vertex: 0
Snipper
    DEAGGREGATE_INPUT = YES
    ENDVERTEXATTR = 0
    SNIPMODE = Vertex
    STARTVERTEXATTR = 0
    -> SpatialRelator [Requestor]
Note: Snipping Mode: Vertex / Starting Vertex: -1 / Ending Vertex: -1
Snipper_2
    DEAGGREGATE_INPUT = YES
    ENDVERTEXATTR = -1
    SNIPMODE = Vertex
    STARTVERTEXATTR = -1
    -> SpatialRelator [Requestor]
Counter
    CNT_ATTR = _count
    DOMAIN = counter
    SCOPE = Global
    START = 0
    -> SpatialRelator [Supplier]
    -> SpatialRelator_2 [Requestor]
SpatialRelator
    AGGREGATE_HANDLING = Yes
    CALC_CARD = No
    CURVE_BOUNDARY_RULE_PARAM = Default Rule
    PREDICATES = TOUCHES
    SUCCESS_ATTR = _related_suppliers
    -> Matcher
Note: Remove duplicate endpoints
Matcher
    BLANK_AND_MISSING_NAMES_TRAITS_DIFFER = No
    CHECK_COORDINATE_SYSTEMS = No
    CNT_ATTR = _match_id
    LENIENT_MATCH = No
    MATCH = FULL
    SINGLE_MATCHED -> SpatialRelator_2 [Supplier]
    NOT_MATCHED -> SpatialRelator_2 [Supplier]
SpatialRelator_2
    AGGREGATE_HANDLING = Yes
    CALC_CARD = No
    CURVE_BOUNDARY_RULE_PARAM = Default Rule
    LIST_ATTRS_TO_INCLUDE = _related_suppliers
    LIST_NAME = _relationships
    PREDICATES = TOUCHES
    SUCCESS_ATTR = _related_suppliers
    -> LineExtender
LineExtender
