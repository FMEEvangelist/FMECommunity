FME workspace LargestRectangle.fmwt
Title: NONE to NONE

Note: Clipper_2 : Candidate
Junction
    -> Junction_2
Note: Original feature
Junction_2
    -> Clipper_2 [CANDIDATE]
Note: Remove any intermediate points
Note: TOLERANCE!
Note: Test and ignore any shape that is already a right-angled triangle
Generalizer
    ALG_TEXT = Douglas (Generalize)
    PRESERVE = No
    PRESERVE_PATHS = No
    TOLERANCE = .1
    -> VertexCounter
Note: Give each object a unique ID
Counter
    CNT_ATTR = _count
    DOMAIN = counter
    SCOPE = Global
    START = 0
    -> Chopper_2
Note: Turn everything into two-point lines
Chopper_2
    DEAGGREGATE_INPUT = Deaggregate
    MAX_VERTICES = 2
    MODE = By Vertex
    REMNANT_ATTR = _remnant
    CHOPPED -> LineExtender
Note: TOLERANCE!
Note: Extend the lines until we are sure we have the entire triangle covered
LineExtender
    LEN = 10
    STRETCHED -> Intersector
Note: Intersect all of the lines
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    GRP_BY = _count
    MEASURE_TYPE = Continuous
    NODE_NUM_ATTR = _node_number
    OV_ATTR = _overlaps
    SEG_ATTR = _segments
    SEPARATE_COLLINEAR_SEGMENTS = No
    INTERSECTED -> AreaBuilder
Note: Build the "triangle"
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    GROUP_BY = _count
    LINES_AS_SEGMENTS = No
    POLY_ACCUM_ATTRS_NAME = Use Attributes From One Feature
    SNAPTYPE_PARAM = None
    AREA -> Clipper_2 [CLIPPER]
Note: Cut the "triangle" out of the original feature.
Clipper_2
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Junction_3
Note: What we want!
Junction_3

Bookmark: Make up a feature...
Creator
    GEOM = <?xml version="1.0" encoding="US_ASCII" standalone="no" ?><geometry><polygon><line><coord x="0" y="0"/><coord x="0" y="10"/><coord x="10" y="10"/><coord x="10" y="0"/><coord x="0" y="0"/></line></polygon></geometry>
    GEOMTYPE = Geometry Object
    NUM = 1
    CREATED -> Dissolver
    CREATED -> Scaler
Scaler
    RASTER_SCALING = Extents
    SCALE_ORIGIN = 0,0
    TEXT_LOC_ONLY = Location and Size
    XSCALE = .2
    YSCALE = .2
    ZSCALE = 1
    SCALED -> Offsetter
Offsetter
    MODE = Cartesian Coordinate
    XOFF = 0
    YOFF = -2
    ZOFF = 0
    OFFSET -> Dissolver
    OFFSET -> Offsetter_2
Offsetter_2
    MODE = Cartesian Coordinate
    XOFF = 10
    YOFF = 6
    ZOFF = 0
    OFFSET -> Dissolver
Dissolver
    ACCUM_INPUT_ATTRS = Use Attributes From One Feature
    CLEANING_TOLERANCE = Automatic
    CONNECT_Z_MODE = First Wins
    DEAGGREGATE_INPUT = Yes
    AREA -> Rotator
Rotator
    ANGLE = 33
    XORIG = 0
    YORIG = 0
    ROTATED -> BoundingBoxReplacer
    ROTATED -> Clipper [CLIPPER]
    ROTATED -> Junction

Bookmark: Create the outer section of the bounding box
BoundingBoxReplacer
    BOXTYPE = 2D Bounding Box
    BOX -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Generalizer

Bookmark: Existing Triangles
VertexCounter
    CNT_ATTR = _vertexcount
    -> Tester
Tester
    BOOL_OP = OR
    TEST_CLAUSE = TEST @Value(_vertexcount) = 4
    TEST_MODE = TEST
    FAILED -> Counter
